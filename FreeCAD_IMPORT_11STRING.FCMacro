"""Import the generated 11-string master STEP into a new FreeCAD document."""

from pathlib import Path

import FreeCAD
import FreeCADGui
import ImportGui
from PySide import QtGui


selected = QtGui.QFileDialog.getExistingDirectory(
    None, "Select the generated cad_build directory"
)
if selected:
    step_path = Path(selected) / "11string_22edo_acoustic_electric_MASTER.step"
    if not step_path.is_file():
        raise FileNotFoundError(f"Master STEP not found: {step_path}")
    document = FreeCAD.newDocument("Guitar11String22EDO")
    ImportGui.insert(str(step_path), document.Name)
    document.recompute()
    FreeCADGui.activeDocument().activeView().viewAxonometric()
    FreeCADGui.activeDocument().activeView().fitAll()
